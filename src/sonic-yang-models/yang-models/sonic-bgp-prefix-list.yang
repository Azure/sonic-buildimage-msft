module sonic-bgp-prefix-list {

    yang-version 1.1;

    namespace "http://github.com/sonic-net/sonic-bgp-prefix-list";
    prefix bgppl;

    import sonic-types {
        prefix stypes;
    }

    import sonic-extension {
        prefix ext;

    import sonic-routing-policy-sets {
        prefix rpolsets;
    }

    description "SONIC Device-specfifc BGP prefix lists data";

    revision 2026-05-18 {
        description "Add optional action, seq, ge and le leaves; require action for seq, ge, and le";
    }

    revision 2025-02-17 {
        description "Updated description and leaves for PREFIX_LIST_LIST";
    }

    revision 2025-02-05 {
        description "Initial revision.";
    }

    container sonic-bgp-prefix-list {

        container PREFIX_LIST {

            description "PREFIX_LIST container consumed in BGP";

            list PREFIX_LIST_LIST {

                description "PREFIX_LIST part of config_db.json with prefix_type and ip-prefix";

                key "prefix_type ip-prefix";

                leaf prefix_type {
                    type string;
                    description "Prefix type";
                }

                leaf ip-prefix {
                    type union {
                        type stypes:sonic-ip4-prefix;
                        type stypes:sonic-ip6-prefix;
                    }
                }

                leaf family {

                    /* family leaf needed for backward compatibility
                       Both ip4 and ip6 address are string in IETF RFC 6021,
                       so must statement can check based on : or ., family
                       should be IPv4 or IPv6 according.
                     */

                    must "(contains(../ip-prefix, ':') and current()='IPv6') or
                        (contains(../ip-prefix, '.') and current()='IPv4')";
                    type stypes:ip-family;
                }

                leaf action {
                    type rpolsets:routing-policy-action-type;
                    description "Permit or deny action for this prefix entry";
                }

                leaf seq {
                    when "../action";
                    type uint32 {
                        range "1..4294967295";
                    }
                    description "Sequence number for ordering prefix list entries. Optional, but should be provided when a specific execution order is needed";
                }

                leaf ge {
                    when "../action";
                    must "(contains(../ip-prefix, '.') and . <= 32) or
                        (contains(../ip-prefix, ':') and . <= 128)" {
                        error-message "ge value must be <= 32 for IPv4 or <= 128 for IPv6";
                    }
                    must ". >= number(substring-after(../ip-prefix, '/'))" {
                        error-message "ge value must be >= prefix length";
                    }
                    type uint8 {
                        range "0..128";
                    }
                    description "Minimum prefix length to match (greater-than-or-equal)";
                }

                leaf le {
                    when "../action";
                    must "(contains(../ip-prefix, '.') and . <= 32) or
                        (contains(../ip-prefix, ':') and . <= 128)" {
                        error-message "le value must be <= 32 for IPv4 or <= 128 for IPv6";
                    }
                    must ". >= number(substring-after(../ip-prefix, '/'))" {
                        error-message "le value must be >= prefix length";
                    }
                    /* If ge is not set, skip this check.
                       If ge is set, enforce le >= ge. */
                    must "not(../ge) or current() >= ../ge" {
                        error-message "le value must be >= ge value";
                    }
                    type uint8 {
                        range "0..128";
                    }
                    description "Maximum prefix length to match (less-than-or-equal)";
                }
            }
        }
        /* end of PREFIX_LIST */
    }
}
