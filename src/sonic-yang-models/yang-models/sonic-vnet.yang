module sonic-vnet {
    yang-version 1.1;
    namespace "http://github.com/sonic-net/sonic-vnet";
    prefix svnet;

    import ietf-yang-types {
        prefix yang;
    }

    import ietf-inet-types {
        prefix inet;
    }

    import sonic-types {
        prefix stypes;
    }

    import sonic-vxlan {
        prefix svxlan;
    }
    organization
        "SONiC";

    contact
        "SONiC";

    description
        "VNET YANG Module for SONiC OS";

    revision 2026-09-15 {
        description
            "Add install_on_kernel leaf to VNET_ROUTE_TUNNEL_LIST.";
    }

    revision 2023-04-25 {
        description
            "First revision.";
    }

    container sonic-vnet {

        container VNET {

            description "config db VNET table";

            list VNET_LIST {

                key "name";

                must "vxlan_tunnel or string-length(vxlan_tunnel_list) > 0" {
                    error-message "Either vxlan_tunnel or a non-empty vxlan_tunnel_list must be configured.";
                }

                leaf name {
                    description "An alphanumaric string to represent the name of the unique vnet";
                    type string {
                        length 1..255;
                    }
                }

                leaf vxlan_tunnel {
                    description "A valid and active vxlan tunnel to be used with this vnet for traffic encapsulation.";
                    type leafref {
                        path "/svxlan:sonic-vxlan/svxlan:VXLAN_TUNNEL/svxlan:VXLAN_TUNNEL_LIST/svxlan:name";
                    }
                }

                leaf vxlan_tunnel_list {
                    description "Comma-separated VXLAN tunnel names. Takes precedence over vxlan_tunnel when non-empty.";
                    type string;
                }

                leaf vni {
                    mandatory true;
                    description "A valid and unique vni which will become part of the encapsulated traffic header.";
                    type stypes:vnid_type;
                }

                leaf peer_list {
                    description "Set of peers";
                    /* Values in leaf list are UNIQUE */
                    type string;
                }

                leaf guid {
                    description "An optional guid.";
                    type string {
                        length 1..255;
                    }
                }

                leaf scope {
                    description "can only be default.";
                    type string {
                        pattern "default" {
                            error-message "Invalid VRF name";
                        }
                    }
                }

                leaf advertise_prefix {
                    description "Flag to enable advertisement of route prefixes belonging to the Vnet.";
                    type  boolean;
                }

                leaf overlay_dmac {
                    description "Overlay Dest MAC address to be used by Vnet ping.";
                    type yang:mac-address;
                }

                leaf src_mac {
                    description "source mac address for the Vnet";
                    type yang:mac-address;
                }
            }
            /* end of list VNET_LIST */
        }
        /* end of container VNET */

        container VNET_ROUTE {

            description "ConfigDB VNET_ROUTE table";

            list VNET_ROUTE_LIST {
                key "vnet_name prefix";

                leaf vnet_name {
                    description "VNET name";
                    type leafref {
                        path "/svnet:sonic-vnet/svnet:VNET/svnet:VNET_LIST/svnet:name";
                    }
                }

                leaf prefix {
                    description "IP prefix in CIDR format (IPv4 or IPv6)";
                    type stypes:sonic-ip-prefix;
                }

                leaf nexthop {
                    description "Nexthop IP addresses (IPv4 or IPv6, comma-separated)";
                    type union {
                        type stypes:ipv4-address-list;
                        type stypes:ipv6-address-list;
                    }
                    mandatory true;
                }

                leaf ifname {
                    description "Interface names";
                    type string;
                    mandatory true;
                }
            }
            /* end of list VNET_ROUTE_LIST */
        }
        /* end of container VNET_ROUTE */

        container VNET_ROUTE_TUNNEL {

            description "ConfigDB VNET_ROUTE_TUNNEL table";
            
            list VNET_ROUTE_TUNNEL_LIST {
                key "vnet_name prefix";

                leaf vnet_name {
                    description "VNET name";
                    type leafref {
                        path "/svnet:sonic-vnet/svnet:VNET/svnet:VNET_LIST/svnet:name";
                    }
                }
                
                leaf prefix {
                    description "IP prefix in CIDR format (IPv4 or IPv6)";
                    type stypes:sonic-ip-prefix;
                }
                
                leaf endpoint {
                    description "Endpoint/nexthop tunnel IPs (IPv4 or IPv6, comma-separated)";
                    type union {
                        type stypes:ipv4-address-list;
                        type stypes:ipv6-address-list;
                    }
                    mandatory true;
                }

                leaf mac_address {
                    description "Inner dest macs in encapsulated packet";
                    type stypes:mac-address-list;
                }

                leaf vni {
                    description "Valid and active vni values in encapsulated packet";
                    type stypes:vnid-list;
                }

                leaf consistent_hashing_buckets {
                    description "Number of consistent hashing buckets to use, if consistent hashing is desired";
                    type uint16;
                }

                leaf metric {
                    description "Value that can be set to categorize or determine the type of route. This value does not affect route behavior.";
                    type uint8;
                }

                leaf install_on_kernel {
                    description "Flag to also program this route into the kernel routing table.";
                    type boolean;
                }
            }
            /* end of list VNET_ROUTE_TUNNEL_LIST */
        }
        /* end of container VNET_ROUTE_TUNNEL */
    }
    /* end of container sonic-vnet */
}
/* end of module sonic-vnet */
